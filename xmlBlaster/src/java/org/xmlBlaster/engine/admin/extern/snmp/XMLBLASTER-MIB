XMLBLASTER-MIB DEFINITIONS ::= BEGIN

-- @(#) $Id: XMLBLASTER-MIB

IMPORTS
    MODULE-IDENTITY, OBJECT-TYPE, NOTIFICATION-TYPE,
    Integer32, Unsigned32, 
    enterprises, mib-2                     FROM SNMPv2-SMI
    DisplayString, TimeStamp, TruthValue   FROM SNMPv2-TC
    MODULE-COMPLIANCE, OBJECT-GROUP        FROM SNMPv2-CONF;

xmlblaster MODULE-IDENTITY
    LAST-UPDATED "200111080000Z"
    ORGANIZATION "Avitech Management Technologies GmbH"
    CONTACT-INFO
            "       Udo Thalmann 

             Postal: Avitech Management Technologies GmbH 
		     Bahnhofsplatz 1
		     88045 Friedrichshafen
		     Germany

             Phone:  ++49-(0)7541/282-122
	     Fax:    ++49-(0)7541/282-399
             Email:  udo.thalmann@avitech.de"
    DESCRIPTION
            "MIB module for managing aviation software from Avitech."
    REVISION      "200111080000Z"
    DESCRIPTION
            "SMIv2 version converted from older MIB definitions."
    ::= { enterprises 11662 }

--
-- The various groups defined within this MIB module.
--

node OBJECT IDENTIFIER ::= { xmlblaster 1 }
trap OBJECT IDENTIFIER ::= { xmlblaster 2 }

--
-- Object definitions.
--

nodeScalar OBJECT IDENTIFIER ::= { node 1 }

numNodes OBJECT-TYPE
    SYNTAX      Unsigned32
    MAX-ACCESS  read-only
    STATUS      current
    DESCRIPTION
            "The actual number of moms in nodeTable."
    ::= { nodeScalar 1 }

nodeTable OBJECT-TYPE
    SYNTAX      SEQUENCE OF NodeEntry
    MAX-ACCESS  not-accessible
    STATUS      current
    DESCRIPTION
        "A table of moms to be monitored.
         The current number of moms is specified by nodeNumber."
    ::= { node 2 }

nodeEntry OBJECT-TYPE
    SYNTAX      NodeEntry
    MAX-ACCESS  not-accessible
    STATUS      current
    DESCRIPTION
            "An entry containing mom specific snmp attributes."
    INDEX   { nodeIndex }
    ::= { nodeTable 1 }

NodeEntry ::=
    SEQUENCE {
        nodeIndex               Unsigned32,
        nodeName                DisplayString,
        nodeUptime              TimeStamp,
        totalMem                Unsigned32,
        usedMem                 Unsigned32,
        freeMem                 Unsigned32,
        hostname                DisplayString,
        port                    Unsigned32,
        numClients              Unsigned32,
        maxClients              Unsigned32,
        clientThreshold         Unsigned32,
        errorLogfile            DisplayString,
        logLevel                INTEGER,
        runLevel                INTEGER
    }

nodeIndex OBJECT-TYPE
    SYNTAX      Unsigned32
    MAX-ACCESS  not-accessible
    STATUS      current
    DESCRIPTION
            "A unique value identifying the mom entry."
    ::= { nodeEntry 1 }

nodeName OBJECT-TYPE
    SYNTAX      DisplayString
    MAX-ACCESS  read-only
    STATUS      current
    DESCRIPTION
            "Name of the mom instance."
    ::= { nodeEntry 2 }

nodeUptime OBJECT-TYPE
    SYNTAX      TimeStamp
    MAX-ACCESS  read-only
    STATUS      current
    DESCRIPTION
            "Mom uptime in seconds."
    ::= { nodeEntry 3 }

totalMem OBJECT-TYPE
    SYNTAX      Unsigned32
    MAX-ACCESS  read-only
    STATUS      current
    DESCRIPTION
            "Total memory on host in bytes."
    ::= { nodeEntry 4 }

usedMem OBJECT-TYPE
    SYNTAX      Unsigned32
    MAX-ACCESS  read-only
    STATUS      current
    DESCRIPTION
            "Used memory on host in bytes."
    ::= { nodeEntry 5 }

freeMem OBJECT-TYPE
    SYNTAX      Unsigned32
    MAX-ACCESS  read-only
    STATUS      current
    DESCRIPTION
            "Free memory on host in bytes."
    ::= { nodeEntry 6 }

hostname OBJECT-TYPE
    SYNTAX      DisplayString
    MAX-ACCESS  read-only
    STATUS      current
    DESCRIPTION
            "Name of the host."
    ::= { nodeEntry 7 }

port OBJECT-TYPE
    SYNTAX      Unsigned32
    MAX-ACCESS  read-write
    STATUS      current
    DESCRIPTION
            "Portnumber."
    ::= { nodeEntry 8 }

numClients OBJECT-TYPE
    SYNTAX      Unsigned32
    MAX-ACCESS  read-only
    STATUS      current
    DESCRIPTION
            "The actual number of mom clients in clientTable."
    ::= { nodeEntry 9 }

maxClients OBJECT-TYPE
    SYNTAX      Unsigned32
    MAX-ACCESS  read-write
    STATUS      current
    DESCRIPTION
            "The maximum number of mom clients in clientTable."
    ::= { nodeEntry 10 }

clientThreshold  OBJECT-TYPE
    SYNTAX      Unsigned32
    MAX-ACCESS  read-write
    STATUS      current
    DESCRIPTION
            "Threshold (%) number of mom clients in clientTable."
    ::= { nodeEntry 11 }

errorLogfile OBJECT-TYPE
    SYNTAX      DisplayString
    MAX-ACCESS  read-write
    STATUS      current
    DESCRIPTION
            "Name of the error logfile."
    ::= { nodeEntry 12 }

logLevel OBJECT-TYPE
    SYNTAX      INTEGER { errors(0), warnings(1), infos(2) }
    MAX-ACCESS  read-write
    STATUS      current
    DESCRIPTION
            "Various degrees of mom log levels i.e. errors, warnings, infos."
    ::= { nodeEntry 13 }

runLevel OBJECT-TYPE
    SYNTAX      INTEGER {halted(0), standby(3), cleanup(6), running(10)}
    MAX-ACCESS  read-write
    STATUS      current
    DESCRIPTION
            "Various degrees of mom run levels."
    ::= { nodeEntry 14 }

connectionTable OBJECT-TYPE 
    SYNTAX      SEQUENCE OF ConnectionEntry
    MAX-ACCESS  not-accessible
    STATUS      current
    DESCRIPTION
        "A table of mom connections."
    ::= { node 3 }

connectionEntry OBJECT-TYPE
    SYNTAX      ConnectionEntry
    MAX-ACCESS  not-accessible
    STATUS      current
    DESCRIPTION
            "An entry containing mom connection specific snmp attributes."
    INDEX   { nodeIndex, connectionIndex }
    ::= { connectionTable 1 }

ConnectionEntry ::=
    SEQUENCE {
        connectionIndex            Unsigned32,
        connectionHost             DisplayString,
        connectionPort             Unsigned32,
        connectionAddress          DisplayString,
        connectionProtocol         INTEGER
    }

connectionIndex OBJECT-TYPE
    SYNTAX      Unsigned32
    MAX-ACCESS  not-accessible
    STATUS      current
    DESCRIPTION
            "A unique value identifying the connection entry."
    ::= { connectionEntry 1 }

connectionHost  OBJECT-TYPE
    SYNTAX      DisplayString
    MAX-ACCESS  read-only
    STATUS      current
    DESCRIPTION
            "Name of the connection host."
    ::= { connectionEntry 2}

connectionPort  OBJECT-TYPE
    SYNTAX      Unsigned32
    MAX-ACCESS  read-only
    STATUS      current
    DESCRIPTION
            "Number of connection port."
    ::= { connectionEntry 3}

connectionAddress  OBJECT-TYPE
    SYNTAX      DisplayString
    MAX-ACCESS  read-only
    STATUS      current
    DESCRIPTION
            "Connection protocol specific address, e.g. http://www.netscape.de/...."
    ::= { connectionEntry 4}

connectionProtocol OBJECT-TYPE
    SYNTAX      INTEGER { bootstrap(0), ior(1), rmi(2), xmlrpc(3), socket(4) }
    MAX-ACCESS  read-only
    STATUS      current
    DESCRIPTION
            "Type of connection protocol i.e. bootstrap, ior, rmi, xmlrpc, socket, etc."
    ::= { connectionEntry 5}

clientTable OBJECT-TYPE 
    SYNTAX      SEQUENCE OF ClientEntry
    MAX-ACCESS  not-accessible
    STATUS      current
    DESCRIPTION
        "A table of mom clients.
         The current number of mom clients is specified by 
         numClients in nodeTable."
    ::= { node 4 }

clientEntry OBJECT-TYPE
    SYNTAX      ClientEntry
    MAX-ACCESS  not-accessible
    STATUS      current
    DESCRIPTION
            "An entry containing mom client specific snmp attributes."
    INDEX   { nodeIndex, clientIndex }
    ::= { clientTable 1 }

ClientEntry ::=
    SEQUENCE {
        clientIndex                Unsigned32,
        clientName                 DisplayString,
        peerType                   INTEGER,
        connectionState            INTEGER,
        clientQueueNumMsgs         Unsigned32,
        clientQueueMaxMsgs         Unsigned32,
        clientQueueThreshold       Unsigned32,
        clearClientQueue           TruthValue,
        numSessions                Unsigned32,
        maxSessions                Unsigned32,
        sessionThreshold           Unsigned32,
        clientUptime               TimeStamp,
        clientDowntime             TimeStamp
    }

clientIndex OBJECT-TYPE
    SYNTAX      Unsigned32
    MAX-ACCESS  not-accessible
    STATUS      current
    DESCRIPTION
            "A unique value identifying the momClient entry."
    ::= { clientEntry 1 }

clientName  OBJECT-TYPE
    SYNTAX      DisplayString
    MAX-ACCESS  read-only
    STATUS      current
    DESCRIPTION
            "Name of the mom session."
    ::= { clientEntry 2}

peerType OBJECT-TYPE
    SYNTAX      INTEGER { client(0), mom(1) }
    MAX-ACCESS  read-only
    STATUS      current
    DESCRIPTION
            "Is peer of type client or mom."
    ::= { clientEntry 3}

connectionState OBJECT-TYPE
    SYNTAX      INTEGER { down(0), up(1) }
    MAX-ACCESS  read-only
    STATUS      current
    DESCRIPTION
            "State of the client connection is down or up."
    ::= { clientEntry 4}

clientQueueNumMsgs  OBJECT-TYPE
    SYNTAX      Unsigned32
    MAX-ACCESS  read-only
    STATUS      current
    DESCRIPTION
            "Actual number of messages in the point-to-point client queue."
    ::= { clientEntry 5 }

clientQueueMaxMsgs  OBJECT-TYPE
    SYNTAX      Unsigned32
    MAX-ACCESS  read-write
    STATUS      current
    DESCRIPTION
            "Maximum number of messages in the point-to-point client queue."
    ::= { clientEntry 6 }

clientQueueThreshold  OBJECT-TYPE
    SYNTAX      Unsigned32
    MAX-ACCESS  read-write
    STATUS      current
    DESCRIPTION
            "Threshold (%) number of  messages in the point-to-point
             client queue."
    ::= { clientEntry 7 }

clearClientQueue  OBJECT-TYPE
    SYNTAX      TruthValue
    MAX-ACCESS  read-write
    STATUS      current
    DESCRIPTION
            "If set to true, the point-to-point client queue is emptied."
    ::= { clientEntry 8 }

numSessions OBJECT-TYPE
    SYNTAX      Unsigned32
    MAX-ACCESS  read-only
    STATUS      current
    DESCRIPTION
            "Actual number of client sessions in sessionTable."
    ::= { clientEntry 9 }

maxSessions OBJECT-TYPE
    SYNTAX      Unsigned32
    MAX-ACCESS  read-write
    STATUS      current
    DESCRIPTION
            "Maximum number of client sessions in sessionTable."
    ::= { clientEntry 10 }

sessionThreshold  OBJECT-TYPE
    SYNTAX      Unsigned32
    MAX-ACCESS  read-write
    STATUS      current
    DESCRIPTION
            "Threshold (%) number of client sessions in sessionTable."
    ::= { clientEntry 11 }

clientUptime OBJECT-TYPE
    SYNTAX      TimeStamp
    MAX-ACCESS  read-only
    STATUS      current
    DESCRIPTION
            "Client connection uptime in seconds."
    ::= { clientEntry 12 }

clientDowntime OBJECT-TYPE
    SYNTAX      TimeStamp
    MAX-ACCESS  read-only
    STATUS      current
    DESCRIPTION
            "Client connection downtime in seconds."
    ::= { clientEntry 13 }

sessionTable OBJECT-TYPE 
    SYNTAX      SEQUENCE OF SessionEntry
    MAX-ACCESS  not-accessible
    STATUS      current
    DESCRIPTION
        "A table of mom sessions.
         The current number of mom sessions is specified by
         numSessions in clientTable."
    ::= { node 5 }

sessionEntry OBJECT-TYPE
    SYNTAX      SessionEntry
    MAX-ACCESS  not-accessible
    STATUS      current
    DESCRIPTION
            "An entry containing mom session specific snmp attributes."
    INDEX   { nodeIndex, clientIndex, sessionIndex }
    ::= { sessionTable 1 }

SessionEntry ::=
    SEQUENCE {
        sessionIndex             Unsigned32,
        sessionName              DisplayString,
        cbQueueNumMsgs           Unsigned32,
        cbQueueMaxMsgs           Unsigned32,
        cbQueueThreshold         Unsigned32,
        clearCbQueue             TruthValue,
        closeSession             TruthValue
    }

sessionIndex OBJECT-TYPE
    SYNTAX      Unsigned32
    MAX-ACCESS  not-accessible
    STATUS      current
    DESCRIPTION
            "A unique value identifying the session entry."
    ::= { sessionEntry 1 }

sessionName  OBJECT-TYPE
    SYNTAX      DisplayString
    MAX-ACCESS  read-only
    STATUS      current
    DESCRIPTION
            "Name of the session."
    ::= { sessionEntry 2}

cbQueueNumMsgs  OBJECT-TYPE
    SYNTAX      Unsigned32
    MAX-ACCESS  read-only
    STATUS      current
    DESCRIPTION
            "Actual number of messages in the callback queue."
    ::= { sessionEntry 3 }

cbQueueMaxMsgs  OBJECT-TYPE
    SYNTAX      Unsigned32
    MAX-ACCESS  read-write
    STATUS      current
    DESCRIPTION
            "Maximum number of messages in the callback queue."
    ::= { sessionEntry 4 }

cbQueueThreshold  OBJECT-TYPE
    SYNTAX      Unsigned32
    MAX-ACCESS  read-write
    STATUS      current
    DESCRIPTION
            "Threshold (%) number of  messages in the callback queue."
    ::= { sessionEntry 5 }

clearCbQueue  OBJECT-TYPE
    SYNTAX      TruthValue
    MAX-ACCESS  read-write
    STATUS      current
    DESCRIPTION
            "If set to true, the callback queue is emptied."
    ::= { sessionEntry 6 }

closeSession  OBJECT-TYPE
    SYNTAX      TruthValue
    MAX-ACCESS  read-write
    STATUS      current
    DESCRIPTION
            "If set to true, the session is closed."
    ::= { sessionEntry 7 }

--
-- Notifications.
--

clientTableThresholdOverflow NOTIFICATION-TYPE
    OBJECTS     { nodeName, numClients, maxClients, clientThreshold } 
    STATUS      current
    DESCRIPTION
            "This notification is generated whenever
             maxClients * clientThreshold < numClients."
    ::= { trap 1 }

clientQueueThresholdOverflow NOTIFICATION-TYPE
    OBJECTS     { clientName, clientQueueNumMsgs, clientQueueMaxMsgs, clientQueueThreshold } 
    STATUS      current
    DESCRIPTION
            "This notification is generated whenever
             maxSessions * sessionThreshold < numSessions."
    ::= { trap 2 }

sessionTableThresholdOverflow NOTIFICATION-TYPE
    OBJECTS     { clientName, numSessions, maxSessions,
                  sessionThreshold } 
    STATUS      current
    DESCRIPTION
            "This notification is generated whenever
             maxSessions * sessionThreshold < numSessions."
    ::= { trap 3 }

cbQueueThresholdOverflow NOTIFICATION-TYPE
    OBJECTS     { sessionName, cbQueueNumMsgs, cbQueueMaxMsgs, cbQueueThreshold }
    STATUS      current
    DESCRIPTION
            "This notification is generated whenever
             cbQueueMaxMsgs * cbQueueThreshold < cbQueueNumMsgs."
    ::= { trap 4 }

END
